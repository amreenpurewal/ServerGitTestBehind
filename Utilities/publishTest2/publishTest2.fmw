FME workspace publishTest2.fmw

Creator
    GEOMTYPE = Geometry Object
    NUM = 1
    CREATED -> HTTPCaller
HTTPCaller
    UPLOAD_FILE = C:\Users\apurewal\Documents\VersionControl\test2.fmw
    TARGET_URL = http://localhost:8080/fmerest/v3/repositories/Samples/items/test.fmw
    AUTH_METHOD = Basic
    TRANSFER_TIMEOUT_LENGTH = 90
    ERROR_ATTR = _error
    USE_COOKIES = No
    AUTH_PASSWORD =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
    UPLOAD_CONTENT_TYPE = Binary (application/octet-stream)
    TARGET_ATTR_ENCODING = auto-detect
    CONNECTION_TIMEOUT_LENGTH = 60
    VERIFY_SSL_CERTIFICATES = Yes
    CUSTOM_HEADERS = Content-Type;application/octet-stream
    STATUS_CODE_ATTR = _http_status_code
    SAVE_FILE = Attribute
    RESPONSE_HEADER_LIST_ATTR = _headers
    HTTP_METHOD = PUT
    UPLOAD_TYPE = Upload From File
    TARGET_ATTR = _response_body
    FOLLOW_REDIRECTS = Yes
    AUTH_USERNAME = admin
    -> Logger
Logger
    MAXCOORDS = 20
    MESSAGE = Feature is:
    MAXFEATS = 20
